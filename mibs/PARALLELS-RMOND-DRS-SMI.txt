-- Parallels HA Specific MIB: Rmond MIB Extension
-- 
-- Copyright (c) 2013, Parallels, Inc.
-- Copyright (c) 2017-2019 Virtuozzo International GmbH. All rights reserved.
-- All rights reserved.
--
-- The contents of this document are subject to change without notice.
--

PARALLELS-SMI DEFINITIONS ::= BEGIN

IMPORTS
	MODULE-IDENTITY, OBJECT-IDENTITY, enterprises
		FROM SNMPv2-SMI;

parallelsMIB MODULE-IDENTITY
	LAST-UPDATED "201304260000Z"
	ORGANIZATION "Parallels, Inc."
	CONTACT-INFO "Alexander Tormasov
			E-mail: adm@parallels.com"
	DESCRIPTION
		"The Structure of Management Information for Parallels products."
	
	REVISION "201304260000Z"	-- 26 April 2013
		DESCRIPTION
		"Initial version"
	::= { enterprises 26171 }
--
-- Parallels MIB tree structure
--

parallelsProducts OBJECT-IDENTITY
	STATUS  current
	DESCRIPTION
		"The root of Parallels's Product OIDs."
	::= { parallelsMIB 1 }

parallelsTraps OBJECT-IDENTITY 
	STATUS  current
	DESCRIPTION
		"The root of Parallels's Trap OIDs."
	::= { parallelsMIB 2 }

END

PARALLELS-RMOND-SMI DEFINITIONS ::= BEGIN

IMPORTS
	MODULE-IDENTITY, OBJECT-TYPE, IpAddress, Unsigned32, Counter32, NOTIFICATION-TYPE, Counter64
		FROM SNMPv2-SMI
	TEXTUAL-CONVENTION, DisplayString, TruthValue, RowStatus
		FROM SNMPv2-TC
	parallelsProducts, parallelsTraps
		FROM PARALLELS-SMI;

rmond_drs	MODULE-IDENTITY
	LAST-UPDATED "201304260000Z"
	ORGANIZATION "Parallels, Inc."
	CONTACT-INFO "Alexander Tormasov
			E-mail: adm@parallels.com"
	DESCRIPTION
		"The Parallels HA interface"

	REVISION "201304260000Z"	-- 26 April 2013
        DESCRIPTION
		"Initial version"
	::= { parallelsProducts 1 }

	rmond_drsLocalVeNumber OBJECT-TYPE
		SYNTAX INTEGER
		MAX-ACCESS read-only
		STATUS current
		DESCRIPTION
			"The number of VEs at the host"
		::= { rmond_drs 101 }

	rmond_drsVeLimit OBJECT-TYPE
		SYNTAX INTEGER
		MAX-ACCESS read-only
		STATUS current
		DESCRIPTION
			"The user configured VE limit"
		::= { rmond_drs 102 }

	rmond_drsLicenseVeNumber OBJECT-TYPE
		SYNTAX INTEGER
		MAX-ACCESS read-only
		STATUS current
		DESCRIPTION
			"The VE limit from the host license"
		::= { rmond_drs 103 }

	rmond_drsLicenseCtNumber OBJECT-TYPE
		SYNTAX INTEGER
		MAX-ACCESS read-only
		STATUS current
		DESCRIPTION
			"The CT limit from the host license"
		::= { rmond_drs 104 }

	rmond_drsLicenseVmNumber OBJECT-TYPE
		SYNTAX INTEGER
		MAX-ACCESS read-only
		STATUS current
		DESCRIPTION
			"The VM limit from the host license"
		::= { rmond_drs 105 }

	rmond_drsLicenseCtUsage OBJECT-TYPE
		SYNTAX INTEGER
		MAX-ACCESS read-only
		STATUS current
		DESCRIPTION
			"The CT usage from the host license"
		::= { rmond_drs 106 }

	rmond_drsLicenseVmUsage OBJECT-TYPE
		SYNTAX INTEGER
		MAX-ACCESS read-only
		STATUS current
		DESCRIPTION
			"The VM usage from the host license"
		::= { rmond_drs 107 }

	rmond_drsSinkTable OBJECT-TYPE	
		SYNTAX SEQUENCE OF RmondSinkEntryType
		MAX-ACCESS not-accessible
		STATUS current
		DESCRIPTION
			"Table of trap subscribers"
		::= { rmond_drs 51 }

	rmond_drsSinkEntry OBJECT-TYPE
		SYNTAX RmondSinkEntryType
		MAX-ACCESS not-accessible
		STATUS current
		DESCRIPTION
			"The trap subscriber parameters"

		INDEX { rmond_drsSinkHost, rmond_drsSinkPort }
		::= { rmond_drsSinkTable 1 }

	RmondSinkEntryType ::= SEQUENCE {
		rmond_drsSinkHost DisplayString,
		rmond_drsSinkPort Unsigned32,
		rmond_drsSinkPeriod Unsigned32,
		rmond_drsSinkLimit Unsigned32,
		rmond_drsSinkAcks Unsigned32,
		rmond_drsSinkStatus RowStatus,
		rmond_drsSinkTicket DisplayString
	}

	rmond_drsSinkHost OBJECT-TYPE
		SYNTAX DisplayString(SIZE(1..128))
		MAX-ACCESS read-only
		STATUS current
		DESCRIPTION
			"The network address of the subscriber"
		::= { rmond_drsSinkEntry 1 }


	rmond_drsSinkPort OBJECT-TYPE
		SYNTAX Unsigned32
		MAX-ACCESS read-only
		STATUS current
		DESCRIPTION
			"The network port of the subscriber"
		::= { rmond_drsSinkEntry 2 }

	rmond_drsSinkPeriod OBJECT-TYPE
		SYNTAX Unsigned32
		MAX-ACCESS read-create
		STATUS current
		DESCRIPTION
			"The time interval between reports"
		::= { rmond_drsSinkEntry 3 }

	rmond_drsSinkLimit OBJECT-TYPE
		SYNTAX Unsigned32
		MAX-ACCESS read-create
		STATUS current
		DESCRIPTION
			"The number of entries in a single notification"
		::= { rmond_drsSinkEntry 4 }

	rmond_drsSinkAcks OBJECT-TYPE
		SYNTAX Unsigned32
		MAX-ACCESS read-create
		STATUS current
		DESCRIPTION
			"Total reports"
		::= { rmond_drsSinkEntry 5 }

	rmond_drsSinkStatus OBJECT-TYPE
		SYNTAX RowStatus
		MAX-ACCESS read-create
		STATUS current
		DESCRIPTION
			"The status of this conceptual row"
		::= { rmond_drsSinkEntry 6 }

	rmond_drsSinkTicket OBJECT-TYPE
		SYNTAX DisplayString(SIZE(1..128))
		MAX-ACCESS read-create
		STATUS current
		DESCRIPTION
			"The opaque user data"
		::= { rmond_drsSinkEntry 7 }

	rmond_drsMetricTable OBJECT-TYPE	
		SYNTAX SEQUENCE OF RmondMetricEntryType
		MAX-ACCESS not-accessible
		STATUS current
		DESCRIPTION
			"Table of metric filters by trap subscribers"
		::= { rmond_drs 52 }

	rmond_drsMetricEntry OBJECT-TYPE
		SYNTAX RmondMetricEntryType
		MAX-ACCESS not-accessible
		STATUS current
		DESCRIPTION
			"The metric parameters"

		INDEX { rmond_drsSinkHost, rmond_drsSinkPort, rmond_drsMetric }
		::= { rmond_drsMetricTable 1 }

	RmondMetricEntryType ::= SEQUENCE {
		rmond_drsMetric OBJECT IDENTIFIER,
		rmond_drsMetricStatus RowStatus
	}

	rmond_drsMetric OBJECT-TYPE
		SYNTAX OBJECT IDENTIFIER
		MAX-ACCESS read-only
		STATUS current
		DESCRIPTION
			"The metric name"
		::= { rmond_drsMetricEntry 1 }

	rmond_drsMetricStatus OBJECT-TYPE
		SYNTAX RowStatus
		MAX-ACCESS read-create
		STATUS current
		DESCRIPTION
			"The status of this conceptual row"
		::= { rmond_drsMetricEntry 2 }


	rmond_drsVeTable OBJECT-TYPE
		SYNTAX SEQUENCE OF RmondVeTableEntryType
		MAX-ACCESS not-accessible
		STATUS current
		DESCRIPTION
			"Table of local VEs"
		::= { rmond_drs 55 }

	rmond_drsVeTableEntry OBJECT-TYPE
		SYNTAX RmondVeTableEntryType
		MAX-ACCESS not-accessible
		STATUS current
		DESCRIPTION
			"The VE parameters"

		INDEX { rmond_drsVeId }
		::= { rmond_drsVeTable 1 }

	RmondVeTableEntryType ::= SEQUENCE {
		rmond_drsVeId DisplayString,
		rmond_drsVeType INTEGER,
		rmond_drsVeName DisplayString,
		rmond_drsVeState INTEGER,
		rmond_drsVePerfectNode DisplayString,
		rmond_drsVeMemoryTotal Counter64,
		rmond_drsVeMemoryUsage Counter64,
		rmond_drsVeSwapTotal Counter64,
		rmond_drsVeSwapUsage Counter64,
		rmond_drsVeCpuNumber INTEGER,
		rmond_drsVeCpuLimit INTEGER,
		rmond_drsVeCpuUnits INTEGER,
		rmond_drsVeCpuSystem INTEGER,
		rmond_drsVeCpuUser INTEGER,
		rmond_drsVeType INTEGER,
		rmond_drsVeUuid DisplayString
	}

	rmond_drsVeId OBJECT-TYPE
		SYNTAX DisplayString(SIZE(1..39))
		MAX-ACCESS read-only
		STATUS current
		DESCRIPTION
			"The VE id"

		::= { rmond_drsVeTableEntry 1 }

	rmond_drsVeName OBJECT-TYPE
		SYNTAX DisplayString(SIZE(1..255))
		MAX-ACCESS read-only
		STATUS current
		DESCRIPTION
			"The VE name"

		::= { rmond_drsVeTableEntry 2 }

	rmond_drsVeState OBJECT-TYPE
                SYNTAX INTEGER {unknown(0),
				stopped(805306369),
				starting(805306370),
				restoring(805306371),
				running(805306372),
				paused(805306373),
				suspending(805306374),
				stopping(805306375),
				compacting(805306376),
				suspended(805306377),
				snapshoting(805306378),
				resetting(805306379),
				pausing(805306380),
				continuing(805306381),
				migrating(805306382),
				deleting(805306383),
				resuming(805306384),
				suspendingsync(805306385),
				reconnecting(805306386),
				mounted(805306387) }

		MAX-ACCESS read-only
		STATUS current
		DESCRIPTION
			"The VE state"

		::= { rmond_drsVeTableEntry 3 }

	rmond_drsVePerfectNode OBJECT-TYPE
		SYNTAX DisplayString(SIZE(1..255))
		MAX-ACCESS read-only
		STATUS current
		DESCRIPTION
			"The perfect node for the VE"

		::= { rmond_drsVeTableEntry 4 }

	rmond_drsVeMemoryTotal OBJECT-TYPE
		SYNTAX Counter64
		MAX-ACCESS read-only
		STATUS current
		DESCRIPTION
			"The memory total for the VE"

		::= { rmond_drsVeTableEntry 5 }

	rmond_drsVeMemoryUsage OBJECT-TYPE
		SYNTAX Counter64
		MAX-ACCESS read-only
		STATUS current
		DESCRIPTION
			"The memory usage for the VE"

		::= { rmond_drsVeTableEntry 6 }

	rmond_drsVeSwapTotal OBJECT-TYPE
		SYNTAX Counter64
		MAX-ACCESS read-only
		STATUS current
		DESCRIPTION
			"The swap total for the VE"

		::= { rmond_drsVeTableEntry 7 }

	rmond_drsVeSwapUsage OBJECT-TYPE
		SYNTAX Counter64
		MAX-ACCESS read-only
		STATUS current
		DESCRIPTION
			"The swap usage for the VE"

		::= { rmond_drsVeTableEntry 8 }

	rmond_drsVeCpuNumber OBJECT-TYPE
		SYNTAX INTEGER
		MAX-ACCESS read-only
		STATUS current
		DESCRIPTION
			"The number of CPU for the VE"

		::= { rmond_drsVeTableEntry 9 }

	rmond_drsVeCpuLimit OBJECT-TYPE
		SYNTAX INTEGER
		MAX-ACCESS read-only
		STATUS current
		DESCRIPTION
			"The CPU limit for the VE"

		::= { rmond_drsVeTableEntry 10 }

	rmond_drsVeCpuUnits OBJECT-TYPE
		SYNTAX INTEGER
		MAX-ACCESS read-only
		STATUS current
		DESCRIPTION
			"The CPU units for the VE"

		::= { rmond_drsVeTableEntry 11 }

	rmond_drsVeCpuSystem OBJECT-TYPE
		SYNTAX INTEGER
		MAX-ACCESS read-only
		STATUS current
		DESCRIPTION
			"The CPU system usage inside the VE"

		::= { rmond_drsVeTableEntry 12 }

	rmond_drsVeCpuUser OBJECT-TYPE
		SYNTAX INTEGER
		MAX-ACCESS read-only
		STATUS current
		DESCRIPTION
			"The CPU user usage inside the VE"

		::= { rmond_drsVeTableEntry 13 }

	rmond_drsVeType OBJECT-TYPE
                SYNTAX INTEGER {vm(0),
				ct(1) }

		MAX-ACCESS read-only
		STATUS current
		DESCRIPTION
			"The VE type"

		::= { rmond_drsVeTableEntry 14 }

	rmond_drsVeUuid OBJECT-TYPE
		SYNTAX DisplayString(SIZE(1..39))
		MAX-ACCESS read-only
		STATUS current
		DESCRIPTION
			"The VE UUID reported by the dispatcher"

		::= { rmond_drsVeTableEntry 15 }

	rmond_drsVeDiskTable OBJECT-TYPE
		SYNTAX SEQUENCE OF RmondVeDiskTableEntryType
		MAX-ACCESS not-accessible
		STATUS current
		DESCRIPTION
			"Table of storages of local VEs"
		::= { rmond_drs 56 }

	rmond_drsVeDiskTableEntry OBJECT-TYPE
		SYNTAX RmondVeDiskTableEntryType
		MAX-ACCESS not-accessible
		STATUS current
		DESCRIPTION
			"The VE storage parameters"

		INDEX { rmond_drsVeId, rmond_drsVeDiskHash1, rmond_drsVeDiskHash2 }
		::= { rmond_drsVeDiskTable 1 }

	RmondVeDiskTableEntryType ::= SEQUENCE {
		rmond_drsVeDiskHash1 Counter32,
		rmond_drsVeDiskHash2 Counter32,
		rmond_drsVeDiskName DisplayString,
		rmond_drsVeDiskTotal Counter64,
		rmond_drsVeDiskUsage Counter64,
		rmond_drsVeDiskReadRequests Counter64,
		rmond_drsVeDiskWriteRequests Counter64,
		rmond_drsVeDiskReadBytes Counter64,
		rmond_drsVeDiskWriteBytes Counter64
	}

	rmond_drsVeDiskName OBJECT-TYPE
		SYNTAX DisplayString(SIZE(1..255))
		MAX-ACCESS read-only
		STATUS current
		DESCRIPTION
			"The VE storage name"

		::= { rmond_drsVeDiskTableEntry 1 }

	rmond_drsVeDiskTotal OBJECT-TYPE
		SYNTAX Counter64
		MAX-ACCESS read-only
		STATUS current
		DESCRIPTION
			"The VE storage capacity"

		::= { rmond_drsVeDiskTableEntry 2 }

	rmond_drsVeDiskUsage OBJECT-TYPE
		SYNTAX Counter64
		MAX-ACCESS read-only
		STATUS current
		DESCRIPTION
			"The VE storage used space"

		::= { rmond_drsVeDiskTableEntry 3 }

	rmond_drsVeDiskReadRequests OBJECT-TYPE
		SYNTAX Counter64
		MAX-ACCESS read-only
		STATUS current
		DESCRIPTION
			"The VE storage read requests rate"

		::= { rmond_drsVeDiskTableEntry 4 }

	rmond_drsVeDiskWriteRequests OBJECT-TYPE
		SYNTAX Counter64
		MAX-ACCESS read-only
		STATUS current
		DESCRIPTION
			"The VE storage write requests rate"

		::= { rmond_drsVeDiskTableEntry 5 }

	rmond_drsVeDiskReadBytes OBJECT-TYPE
		SYNTAX Counter64
		MAX-ACCESS read-only
		STATUS current
		DESCRIPTION
			"The VE storage read rate"

		::= { rmond_drsVeDiskTableEntry 6 }

	rmond_drsVeDiskWriteBytes OBJECT-TYPE
		SYNTAX Counter64
		MAX-ACCESS read-only
		STATUS current
		DESCRIPTION
			"The VE storage write rate"

		::= { rmond_drsVeDiskTableEntry 7 }

	rmond_drsVeDiskHash1 OBJECT-TYPE
		SYNTAX Counter32
		MAX-ACCESS read-only
		STATUS current
		DESCRIPTION
			"The low-order 32 bits of the device name hash"

		::= { rmond_drsVeDiskTableEntry 8 }

	rmond_drsVeDiskHash2 OBJECT-TYPE
		SYNTAX Counter32
		MAX-ACCESS read-only
		STATUS current
		DESCRIPTION
			"The high-order 32 bits of the device name hash"

		::= { rmond_drsVeDiskTableEntry 9 }

	rmond_drsVeNetworkTable OBJECT-TYPE
		SYNTAX SEQUENCE OF RmondVeNetworkTableEntryType
		MAX-ACCESS not-accessible
		STATUS current
		DESCRIPTION
			"Table of network interfaces of local VEs"
		::= { rmond_drs 57 }

	rmond_drsVeNetworkTableEntry OBJECT-TYPE
		SYNTAX RmondVeNetworkTableEntryType
		MAX-ACCESS not-accessible
		STATUS current
		DESCRIPTION
			"The VE network interface parameters"

		INDEX { rmond_drsVeId, rmond_drsVeNetworkInterface }
		::= { rmond_drsVeNetworkTable 1 }

	RmondVeNetworkTableEntryType ::= SEQUENCE {
		rmond_drsVeNetworkInterface DisplayString,
		rmond_drsVeNetworkInBytes Counter64,
		rmond_drsVeNetworkOutBytes Counter64,
		rmond_drsVeNetworkInPackets Counter64,
		rmond_drsVeNetworkOutPackets Counter64,
		rmond_drsVeNetworkMacAddress DisplayString
	}

	rmond_drsVeNetworkInterface OBJECT-TYPE
		SYNTAX DisplayString(SIZE(1..255))
		MAX-ACCESS read-only
		STATUS current
		DESCRIPTION
			"The VE network interface name"

		::= { rmond_drsVeNetworkTableEntry 1 }

	rmond_drsVeNetworkInBytes OBJECT-TYPE
		SYNTAX Counter64
		MAX-ACCESS read-only
		STATUS current
		DESCRIPTION
			"The VE network interface input rate"

		::= { rmond_drsVeNetworkTableEntry 2 }

	rmond_drsVeNetworkOutBytes OBJECT-TYPE
		SYNTAX Counter64
		MAX-ACCESS read-only
		STATUS current
		DESCRIPTION
			"The VE network interface output rate"

		::= { rmond_drsVeNetworkTableEntry 3 }

	rmond_drsVeNetworkInPackets OBJECT-TYPE
		SYNTAX Counter64
		MAX-ACCESS read-only
		STATUS current
		DESCRIPTION
			"The VE network interface input packet rate"

		::= { rmond_drsVeNetworkTableEntry 4 }

	rmond_drsVeNetworkOutPackets OBJECT-TYPE
		SYNTAX Counter64
		MAX-ACCESS read-only
		STATUS current
		DESCRIPTION
			"The VE network interface output packet rate"

		::= { rmond_drsVeNetworkTableEntry 5 }

	rmond_drsVeNetworkMacAddress OBJECT-TYPE
		SYNTAX DisplayString(SIZE(1..12))
		MAX-ACCESS read-only
		STATUS current
		DESCRIPTION
			"A MAC address of the VE network interface"

		::= { rmond_drsVeNetworkTableEntry 6 }

	rmond_drsVeVCpuTable OBJECT-TYPE
		SYNTAX SEQUENCE OF RmondVeVCpuTableEntryType
		MAX-ACCESS not-accessible
		STATUS current
		DESCRIPTION
			"Table of virtual CPUs of local VEs"
		::= { rmond_drs 58 }

	rmond_drsVeVCpuTableEntry OBJECT-TYPE
		SYNTAX RmondVeVCpuTableEntryType
		MAX-ACCESS not-accessible
		STATUS current
		DESCRIPTION
			"The VE virtual CPU parameters"

		INDEX { rmond_drsVeId, rmond_drsVeVCpuOrdinal }
		::= { rmond_drsVeVCpuTable 1 }

	RmondVeVCpuTableEntryType ::= SEQUENCE {
		rmond_drsVeVCpuOrdinal INTEGER,
		rmond_drsVeVCpuTime Counter64
	}

	rmond_drsVeVCpuOrdinal OBJECT-TYPE
		SYNTAX INTEGER
		MAX-ACCESS read-only
		STATUS current
		DESCRIPTION
			"The VE virtual CPU ordinal"

		::= { rmond_drsVeVCpuTableEntry 1 }

	rmond_drsVeVCpuTime OBJECT-TYPE
		SYNTAX Counter64
		MAX-ACCESS read-only
		STATUS current
		DESCRIPTION
			"The VE virtual CPU execution time in nanoseconds"

		::= { rmond_drsVeVCpuTableEntry 2 }

	rmond_drsTrap NOTIFICATION-TYPE
		STATUS  current
		DESCRIPTION
			"The rmond_drs periodic notification"

		::= { parallelsTraps 51 }

END
